import csv
import os
import FreeCAD as App
import Import

# --- CONFIGURATION ---
csv_path = r"C:\Users\murra\PycharmProjects\pythonProject1\physics\Code\lhs_simulations.csv"
output_folder = r"C:\Users\murra\PycharmProjects\pythonProject1\physics\Misc\STEP Files\FinrayLHSVariants"

if not os.path.exists(output_folder):
    os.makedirs(output_folder)

doc = App.activeDocument()
spreadsheet = doc.getObject("Spreadsheet")
body = doc.getObject("Fusion")

with open(csv_path, mode='r') as file:
    reader = csv.DictReader(file)

    for row in reader:
        # Finray: baseSize, externalBeamWidth, internalBeamSpacing, internalBeamSize
        # Purdue VSG: hardLinkHeight, softLinkHeight, baseSize, hardLinkAngle
        # A-shaped: beamLength, beamHeight, externalBeamWidth, internalBeamWidth
        spreadsheet.set("baseSize", row["baseSize"])
        spreadsheet.set("externalBeamWidth", row["externalBeamWidth"])
        spreadsheet.set("beamSpacing", row["internalBeamSpacing"])
        spreadsheet.set("beamSize", row["internalBeamSize"])

        doc.recompute()
        
        if not body.Shape.isValid():
            print("Conflict detected; exiting for loop")
            break

        filename = f"{row['baseSize']}-{row['externalBeamWidth']}-{row['internalBeamSpacing']}-{row['internalBeamSize']}.step"
        full_output_path = os.path.join(output_folder, filename)

        Import.export([body], full_output_path)

        print(f"Successfully exported: {filename}")

print("All variations generated successfully!")
